NodeTree DEFINITIONS AUTOMATIC TAGS ::= BEGIN

-- ===========================================================================
-- Protocol version note
-- ===========================================================================
--
-- This revision replaces the earlier UDP-only version of the protocol
-- (Get / Response as a bare SEQUENCE OF Node) with a session-oriented
-- protocol over QUIC, using QUIC's unreliable DATAGRAM extension
-- (RFC 9221) as the substrate for an application-level reliable-but-
-- UNORDERED delivery layer (see SummaryAck below). The earlier version
-- was never wire-compatible with this one (see goimpl/, the Go/QUIC
-- implementation this schema now serves).
--
-- Every message that carries application data (Get, Set, Create, Query,
-- Response) carries its own `sequenceNumber`, starting at 1 and
-- monotonically increasing per sender per QUIC connection, independent
-- per direction (client->server and server->client each have their own
-- sequence space). This is the unit SummaryAck acknowledges and retransmission
-- keys off of. SummaryAck itself is not sequence-numbered or itself
-- acknowledged, the same way a bare ACK isn't ACKed in TCP/SCTP/QUIC's
-- own loss recovery.

-- ===========================================================================
-- NodePointer / NodeValue / Node
-- ===========================================================================

-- The context tag is the pointer kind: 0 = absolute, 1 = offset, 2 = none.
--
-- An absolute pointer is a UTF8String holding a match expression:
--
--     request    = expression [ "@" resume-index ]
--     expression = 1*( [ "/" ] key-regexp [ "=" value-regexp ] )
--
-- Each element matches a node by its key and, optionally, by its value.
-- The regexp dialect is left to the implementation; a literal "/", "=",
-- or "@" inside a regexp must be escaped with "\". The optional
-- "@<index>" suffix is a continuation cursor into `expression`'s own
-- deterministic flattened result (see Response, below).
--
-- An offset pointer is a signed list-position delta, meaningful only
-- inside a Response's own flattened `nodes` list (never sent by a
-- client): the server's own encoding of "the next entry over there".
--
-- `none` is an explicit "no pointer", used when a client needs to SET
-- firstChild/nextSibling to "nothing" (e.g. deleting a node by
-- relinking around it, see Set, below). It is distinct from an offset
-- of 0, which is a server-internal flattening sentinel, not something
-- a client should ever need to construct itself.

NodePointer ::= CHOICE {
    absolute  [0] UTF8String,
    offset    [1] INTEGER,
    none      [2] NULL
}

-- Typed leaf values, deliberately modeled on SNMP's SMIv2 ObjectSyntax
-- (RFC 2578: INTEGER, OCTET STRING, Counter32, Unsigned32/Gauge32,
-- TimeTicks, Counter64), since this protocol is SNMP-adjacent by
-- design. `real` is NOT part of classic SNMP; it's added because
-- aggregation results (mean, standard deviation, percentiles, see
-- Query) are inherently fractional even when the source samples were
-- integers, and the protocol needs somewhere to put that.
--
-- `real` is encoded as an OCTET STRING containing exactly 8 bytes: an
-- IEEE 754 binary64 value, big-endian, NOT ASN.1's own REAL type.
-- BER's REAL encoding is fully supported by common BER tooling
-- (verified), but Go's stdlib encoding/asn1 has no REAL support
-- at all, and hand-rolling BER REAL parsing in Go was judged not worth
-- the risk for what's ultimately just "one double." A fixed 8-byte
-- OCTET STRING is trivial and robust in both languages.

NodeValue ::= CHOICE {
    integer32    [0] INTEGER (-2147483648..2147483647),
    unsigned32   [1] INTEGER (0..4294967295),              -- Gauge32/Unsigned32
    counter32    [2] INTEGER (0..4294967295),              -- wraps at 2^32
    counter64    [3] INTEGER (0..18446744073709551615),    -- wraps at 2^64
    timeTicks    [4] INTEGER (0..4294967295),               -- hundredths of a second
    octetString  [5] OCTET STRING,                          -- opaque bytes / text; not aggregatable numerically
    real         [6] OCTET STRING (SIZE(8)),                -- IEEE 754 binary64, big-endian; see note above
    noValue      [7] NULL                                    -- explicit "no value" (e.g. a pure container node)
}

Node ::= SEQUENCE {
    key          UTF8String,
    value        NodeValue,
    firstChild   NodePointer,
    nextSibling  NodePointer
}

-- ===========================================================================
-- Requests
-- ===========================================================================

Get ::= SEQUENCE {
    sequenceNumber  INTEGER,
    target          NodePointer
}

-- One target-expression plus field-update within a Set request.
-- `target` uses the same match-expression grammar as an absolute
-- NodePointer (regex-based key/value segments; see NodePointer, above)
-- and may match zero or more nodes.
--
-- newValue is applied to every node `target` matches (a no-op if it
-- matches none). newFirstChild/newNextSibling/newParent are
-- structural, single-node operations: `target` MUST resolve to exactly
-- one node when any of the three is present (an error otherwise),
-- since relinking a shared pointer across multiple nodes isn't a
-- well-defined tree operation. Each field is independently optional:
-- omitted means "leave this alone". A NodePointer field can be
-- explicitly cleared by supplying `none` (NodePointer's none arm).
--
-- newParent, if present, reparents `target` itself to become the new
-- last child of whatever `newParent` resolves to (also exactly one
-- node, anywhere in the tree; `none`/offset are not meaningful here,
-- hence UTF8String rather than NodePointer). `target` must currently be
-- one of this session's own staged nodes under NewNodes (see Create,
-- above), an error otherwise, and newParent's resolved node must not
-- be `target` itself or a descendant of it (that would create a
-- cycle).
--
-- This is how a client commits a subtree staged via Create into live
-- config: build it under NewNodes across as many Create calls as
-- needed, then attach its root with one Set carrying newParent.
-- Nothing staged under NewNodes is reachable from any other part of
-- the tree until this makes it so, which covers NETCONF's candidate/
-- commit gap for NEW subtrees specifically. It does NOT give staged,
-- deferred edits to EXISTING live values (an ordinary Set targeting a
-- live node still applies immediately, not on some later commit), nor
-- an explicit discard/validate step; an unattached staged subtree
-- simply sits under NewNodes until the session ends.

SetEdit ::= SEQUENCE {
    target          UTF8String,
    newValue        NodeValue OPTIONAL,
    newFirstChild   NodePointer OPTIONAL,
    newNextSibling  NodePointer OPTIONAL,
    newParent       UTF8String OPTIONAL
}

-- Applies every edit in `edits`, atomically: every target is resolved
-- against the SAME pre-request tree state (so an earlier edit in the
-- list never changes what a later edit's target matches), and if any
-- edit fails validation, a bad expression or a structural edit whose
-- target doesn't resolve to exactly one node, none of the edits in the
-- request are applied.
--
-- To delete a node, use Delete, below: newFirstChild/newNextSibling
-- remain available here for other structural edits (e.g. reordering
-- children), but the server now computes deletion's own relinking
-- itself, so a client no longer needs to.

Set ::= SEQUENCE {
    sequenceNumber  INTEGER,
    edits           SEQUENCE OF SetEdit
}

-- Deletes every node matched by any expression in `targets` (same
-- match-expression grammar as SetEdit.target/Get). For each deleted
-- node the server itself removes it from its parent's child list; the
-- client only needs to address the node it wants gone, not compute
-- which sibling/parent pointer to relink around it. The tree root
-- cannot be deleted (a target resolving to it is an error). Like Set,
-- every target is resolved against the same pre-request tree state.

Delete ::= SEQUENCE {
    sequenceNumber  INTEGER,
    targets         SEQUENCE OF UTF8String
}

-- Creates a new node under this session's own staged
-- "/Sessions/Connection-ID=<session-id>/NewNodes" subtree (see SESSION
-- PATHS, below), appended as the parent's last child. By default the
-- parent is NewNodes itself; `parent`, if given, must resolve to
-- exactly one node that is NewNodes or one of its own descendants (an
-- error otherwise), letting a client build an arbitrarily deep
-- subtree entirely in private staging space via repeated Create calls,
-- before attaching it to live config in one step with SetEdit's
-- newParent, below. The server responds with a Response whose `nodes`
-- contains exactly the one newly created node.

Create ::= SEQUENCE {
    sequenceNumber  INTEGER,
    key             UTF8String,
    value           NodeValue OPTIONAL,  -- omitted = noValue container node
    parent          UTF8String OPTIONAL  -- omitted = directly under NewNodes
}

-- Aggregation, applicable only to numeric NodeValue kinds (everything
-- except octetString/noValue); percentile's parameter is 0..100
-- (e.g. 95 for P95).

AggregationMethod ::= CHOICE {
    min         [0] NULL,
    max         [1] NULL,
    mean        [2] NULL,
    stdDev      [3] NULL,
    percentile  [4] INTEGER (0..100)
}

-- How Query decides when to (re-)sample nodeExpression:
--
--   once      perform exactly one collection pass immediately, ignoring
--             aggregationInterval/transferInterval's recurring cadence
--             (a single sample is aggregated, if requested, as one
--             degenerate window, and the result is transferred once).
--   interval  re-evaluate nodeExpression every `interval` seconds
--             (must be > 0) and sample matching nodes' values, whether
--             or not they changed; suitable for a regular telemetry
--             cadence (gNMI's Subscribe STREAM+SAMPLE mode).
--   onChange  re-evaluate nodeExpression whenever the server's tree is
--             mutated (Set/Create), but only forward a sample when a
--             matched node's value actually differs from the last one
--             reported for that key (or the key is newly matched);
--             no polling interval, event-triggered (gNMI's Subscribe
--             STREAM+ON_CHANGE mode). The first evaluation after the
--             Query starts always reports every currently-matched
--             value, establishing a baseline the way ON_CHANGE
--             subscriptions conventionally do. A key that stops
--             matching (e.g. its node is deleted) is not reported as a
--             removal: there is currently no delete/tombstone concept
--             in QueryResults, only additions.

CollectionMode ::= CHOICE {
    once      [0] NULL,
    interval  [1] INTEGER,
    onChange  [2] NULL
}

-- A recurring (or one-shot) collection query against `nodeExpression`.
--
--   collectionMode        see CollectionMode, above.
--   aggregationInterval   how often (seconds) to reduce the samples
--                         collected so far via aggregationMethod.
--                         Omitted: no aggregation, raw samples are what
--                         gets transferred.
--   aggregationMethod     required iff aggregationInterval is present.
--   transferInterval      how often (seconds) accumulated results (raw
--                         samples, or aggregation outputs) are
--                         materialized as a timestamp-rooted subtree
--                         under this query's own node in this session's
--                         "/Sessions/Connection-ID=<session-id>/QueryResults"
--                         subtree and pushed to the client as a
--                         Response carrying that same subtree (see
--                         SESSION PATHS, below). Required (> 0) unless
--                         collectionMode is `once`.

Query ::= SEQUENCE {
    sequenceNumber       INTEGER,
    nodeExpression       UTF8String,
    collectionMode       CollectionMode,
    aggregationInterval  INTEGER OPTIONAL,
    aggregationMethod    AggregationMethod OPTIONAL,
    transferInterval     INTEGER
}

-- ===========================================================================
-- Responses
-- ===========================================================================

-- `inReplyTo` is the sequenceNumber of the request this Response is
-- associated with: for Get/Set/Create, the request being answered; for
-- a Query's periodic pushes, the originating Query's own
-- sequenceNumber (the same value for every push that query produces,
-- so the client can tell which active query a given push belongs to).
--
-- On error, `error` is TRUE, `errorNode` is an absolute NodePointer to
-- the ErrorNode the server created under this session's own
-- "/Sessions/Connection-ID=<session-id>/Errors" subtree (see SESSION
-- PATHS, below) describing what went wrong, and `nodes` is empty.

Response ::= SEQUENCE {
    sequenceNumber  INTEGER,
    inReplyTo       INTEGER,
    error           BOOLEAN,
    errorNode       NodePointer OPTIONAL,
    nodes           SEQUENCE OF Node
}

-- ===========================================================================
-- Reliability: SummaryAck
-- ===========================================================================
--
-- QUIC DATAGRAM frames (RFC 9221) are unordered and NOT retransmitted
-- by QUIC itself, though they remain congestion-controlled and are
-- "ack-eliciting" at the QUIC layer. Node data tolerates arbitrary
-- reordering (each Node is independently meaningful, and a Response's
-- flattened `nodes` are reassembled by index via firstChild/
-- nextSibling, not by arrival order), so this protocol deliberately
-- does NOT use QUIC streams (reliable but strictly ordered) for
-- application data. Instead, each datagram-carried message above is
-- reliably delivered via this thin application-level layer: the
-- receiver periodically reports which sequenceNumbers (per direction)
-- it has received, as a compact list of inclusive ranges; the sender
-- retransmits whatever hasn't been acknowledged after a timeout.

SequenceRange ::= SEQUENCE {
    first  INTEGER,
    last   INTEGER   -- inclusive; first == last acknowledges one sequenceNumber
}

SummaryAck ::= SEQUENCE {
    received  SEQUENCE OF SequenceRange
}

-- ===========================================================================
-- The envelope actually carried in each QUIC DATAGRAM frame
-- ===========================================================================

NodeTreeMessage ::= CHOICE {
    get         [0] Get,
    set         [1] Set,
    create      [2] Create,
    query       [3] Query,
    response    [4] Response,
    summaryAck  [5] SummaryAck,
    delete      [6] Delete
}

-- ===========================================================================
-- SESSION PATHS (convention, not a wire type)
-- ===========================================================================
--
-- Every accepted QUIC connection gets a server-generated session id
-- (NOT literally the QUIC-protocol-level Connection ID: quic-go's
-- public API in the version used here doesn't cleanly expose that
-- value outside its qlog Tracer hook, and the wire CID isn't even
-- stable across a connection's lifetime, it rotates during path
-- migration. A server-generated id is used instead, filling the same
-- role.). That session's own three virtual subtrees, created lazily on
-- first use, live at:
--
--     /Sessions/Connection-ID=<session-id>/NewNodes       (Create)
--     /Sessions/Connection-ID=<session-id>/Errors         (errors)
--     /Sessions/Connection-ID=<session-id>/QueryResults   (Query)
--
-- Note for anyone constructing an expression that reaches into one of
-- these paths: the literal key "Connection-ID=<session-id>" contains
-- an unescaped "=", which the expression grammar above treats as a
-- key/value delimiter; write it as "Connection-ID\=<session-id>" in an
-- expression.
--
-- Each Query, on registration (before its first push, if any), gets its
-- own subcontainer under QueryResults, holding only that query's pushed
-- results:
--
--     .../QueryResults/Query-SequenceNumber=<query's own sequenceNumber>
--
-- Each transfer (each time accumulated results are pushed, including the
-- single one of a `once` query) adds one subtree to that node, rooted at a
-- node whose key is the transfer's timestamp:
--
--     .../Query-SequenceNumber=<n>/2026-10-05T13:04:49.091716000Z
--         <sampled key>   value
--         <sampled key>   value   (a key sampled more than once repeats)
--         ...
--
-- The timestamp is the server's UTC clock when the transfer was assembled,
-- always formatted "YYYY-MM-DDTHH:MM:SS.nnnnnnnnnZ" (fixed width, so keys
-- sort in time order), and strictly later than the query's previous one.
-- It is the time of the transfer, not of each sample: a recurring query
-- may have collected the values anywhere in the interval before it. The
-- root has no value; the leaves are ordered by key, and values for the
-- same key keep their collection order.
--
-- The pushed Response carries exactly that subtree, flattened the same way
-- as a Get result (root first, firstChild/nextSibling offsets). A subtree
-- too big for one datagram is cut like a Get result is, with absolute
-- continuation pointers into the materialized path above
-- (".../<timestamp>@<index>"), which the client fetches with ordinary Gets.
-- Because the subtree stays in session state, a client that loses a push
-- can also read it back from there, until it is deleted.
--
-- Deleting that node (an ordinary Delete targeting it, or a broader
-- Delete/Set that detaches it or an ancestor of it) cancels the query;
-- a Delete matching every one of them at once, such as
-- ".../QueryResults/.*", cancels all of the session's queries. (The
-- QueryResults container itself cannot be deleted, see ACCESS CONTROL,
-- below.) Cancelling: the server stops its collect/aggregate/
-- transfer goroutine, same as if the session had disconnected. This is
-- per-query cancellation without a dedicated message: a client that
-- wants to stop watching something was already going to want its
-- accumulated results gone too, and Delete already exists and already
-- means "make this go away." A completed ONCE query has no goroutine
-- left to cancel; deleting its results node after the fact is just
-- ordinary cleanup.

-- ===========================================================================
-- ACCESS CONTROL (convention, not a wire type)
-- ===========================================================================
--
-- Identity. The QUIC/TLS handshake authenticates the peer. A server that
-- requires client certificates (mutual TLS) takes the CommonName of the
-- client's verified certificate as its identity; a server that doesn't
-- treats every client as "anonymous". Identity is fixed for the life of
-- the connection.
--
-- Authorization. Every node a request touches is checked, not the request
-- text: expressions are regexes, so what they match is only known against
-- the tree. A node's path is "/" followed by its keys from the root
-- joined by "/", and an operation is one of:
--
--     read    the node may be seen, and matched by a value predicate
--     write   its value may change, its children may be relinked, or a
--             staged subtree may be attached beneath it (newParent)
--     delete  it may be removed, or dropped by a relink
--
-- What each message needs:
--
--     Get, Query   read. Nodes the identity may not read are simply absent
--                  from results, at every depth. A value predicate is only
--                  ever tested against a readable node, so it cannot be
--                  used to probe data the identity could not read.
--     Set          every target and pointer target is resolved only
--                  through what the identity can read (so an unreadable
--                  node looks exactly like a missing one), then: write on
--                  each node whose value changes and on a structurally
--                  edited target; write on a newParent destination; and
--                  delete on every node a newFirstChild/newNextSibling
--                  relink would drop, with everything beneath it.
--     Delete       delete on each matched node and on everything beneath
--                  it.
--
-- A refused request fails as a whole, with nothing applied, as a Response
-- whose error node has the code "PermissionDenied". Nothing here changes
-- the wire format.
--
-- Built-in rules for the server-managed /Sessions subtree apply to every
-- identity and cannot be loosened by any policy: /Sessions itself is
-- readable, so a client can find its own session; another session's
-- subtree is invisible and untouchable; this session's own root and its
-- NewNodes, Errors and QueryResults containers can be read but not
-- changed or deleted (the server holds direct references to them);
-- beneath NewNodes everything is open to the session, since it is private
-- staging space; beneath Errors and QueryResults nodes can be read and
-- deleted but not written, since the server owns their content, while
-- deleting a query's results node is how it is cancelled.
--
-- Everything else is decided by an operator-supplied policy: per identity
-- read, write and delete path patterns (write and delete imply read),
-- plus a global read-only list that no identity can write or delete. With
-- no policy the server is in open mode: anything outside /Sessions is
-- allowed. A policy denies by default.

END
